-- IEEE 1609.2 Base Standard for Wireless Access in Vehicular Environments (WAVE)
-- Security Services for Applications and Management Messages
-- Based on IEEE Std 1609.2-2016

IEEE1609Dot2 DEFINITIONS AUTOMATIC TAGS ::= BEGIN

EXPORTS ALL;

-- =============================================================================
-- BASIC TYPES
-- =============================================================================

Uint3 ::= INTEGER (0..7)
Uint8 ::= INTEGER (0..255)
Uint16 ::= INTEGER (0..65535)
Uint32 ::= INTEGER (0..4294967295)
Uint64 ::= INTEGER (0..18446744073709551615)

SequenceOfUint8 ::= SEQUENCE OF Uint8
SequenceOfUint16 ::= SEQUENCE OF Uint16

Opaque ::= OCTET STRING

HashedId3 ::= OCTET STRING (SIZE(3))
HashedId8 ::= OCTET STRING (SIZE(8))
HashedId10 ::= OCTET STRING (SIZE(10))
HashedId32 ::= OCTET STRING (SIZE(32))

Time32 ::= Uint32
Time64 ::= Uint64

-- =============================================================================
-- GEOGRAPHIC REGION
-- =============================================================================

GeographicRegion ::= CHOICE {
    circularRegion      CircularRegion,
    rectangularRegion   SequenceOfRectangularRegion,
    polygonalRegion     PolygonalRegion,
    identifiedRegion    SequenceOfIdentifiedRegion,
    ...
}

CircularRegion ::= SEQUENCE {
    center      TwoDLocation,
    radius      Uint16
}

RectangularRegion ::= SEQUENCE {
    northWest   TwoDLocation,
    southEast   TwoDLocation
}

SequenceOfRectangularRegion ::= SEQUENCE OF RectangularRegion

PolygonalRegion ::= SEQUENCE SIZE(3..MAX) OF TwoDLocation

TwoDLocation ::= SEQUENCE {
    latitude    Latitude,
    longitude   Longitude
}

Latitude ::= NinetyDegreeInt
Longitude ::= OneEightyDegreeInt

NinetyDegreeInt ::= INTEGER (-900000000..900000001)
OneEightyDegreeInt ::= INTEGER (-1799999999..1800000001)
KnownLatitude ::= INTEGER (-900000000..900000000)
KnownLongitude ::= INTEGER (-1799999999..1800000000)
UnknownLatitude ::= INTEGER (900000001)
UnknownLongitude ::= INTEGER (1800000001)

IdentifiedRegion ::= CHOICE {
    countryOnly           CountryOnly,
    countryAndRegions     CountryAndRegions,
    countryAndSubregions  CountryAndSubregions,
    ...
}

SequenceOfIdentifiedRegion ::= SEQUENCE OF IdentifiedRegion

CountryOnly ::= Uint16
CountryAndRegions ::= SEQUENCE {
    countryOnly    CountryOnly,
    regions        SequenceOfUint8
}
CountryAndSubregions ::= SEQUENCE {
    countryOnly    CountryOnly,
    regionAndSubregions  SequenceOfRegionAndSubregions
}
RegionAndSubregions ::= SEQUENCE {
    region         Uint8,
    subregions     SequenceOfUint16
}
SequenceOfRegionAndSubregions ::= SEQUENCE OF RegionAndSubregions

-- =============================================================================
-- VALIDITY PERIOD
-- =============================================================================

ValidityPeriod ::= SEQUENCE {
    start       Time32,
    duration    Duration
}

Duration ::= CHOICE {
    microseconds     Uint16,
    milliseconds     Uint16,
    seconds          Uint16,
    minutes          Uint16,
    hours            Uint16,
    sixtyHours       Uint16,
    years            Uint16
}

-- =============================================================================
-- SUBJECT ASSURANCE
-- =============================================================================

SubjectAssurance ::= OCTET STRING (SIZE(1))

-- =============================================================================
-- SERVICE SPECIFIC PERMISSIONS (SSP)
-- =============================================================================

PsidSsp ::= SEQUENCE {
    psid    Psid,
    ssp     ServiceSpecificPermissions OPTIONAL
}

SequenceOfPsidSsp ::= SEQUENCE OF PsidSsp

Psid ::= INTEGER (0..MAX)
SequenceOfPsid ::= SEQUENCE OF Psid

ServiceSpecificPermissions ::= CHOICE {
    opaque              OCTET STRING (SIZE(0..MAX)),
    bitmapSsp           BitmapSsp,
    ...
}

BitmapSsp ::= OCTET STRING (SIZE(0..31))

-- =============================================================================
-- PSID GROUP PERMISSIONS
-- =============================================================================

PsidGroupPermissions ::= SEQUENCE {
    subjectPermissions  SubjectPermissions,
    minChainLength      INTEGER DEFAULT 1,
    chainLengthRange    INTEGER DEFAULT 0,
    eeType              EndEntityType DEFAULT '80'H
}

SequenceOfPsidGroupPermissions ::= SEQUENCE OF PsidGroupPermissions

SubjectPermissions ::= CHOICE {
    explicit            SequenceOfPsidSspRange,
    all                 NULL,
    ...
}

SequenceOfPsidSspRange ::= SEQUENCE OF PsidSspRange

PsidSspRange ::= SEQUENCE {
    psid         Psid,
    sspRange     SspRange OPTIONAL
}

SspRange ::= CHOICE {
    opaque              SequenceOfOctetString,
    all                 NULL,
    bitmapSspRange      BitmapSspRange,
    ...
}

BitmapSspRange ::= SEQUENCE {
    sspValue    OCTET STRING (SIZE(1..32)),
    sspBitmask  OCTET STRING (SIZE(1..32))
}

SequenceOfOctetString ::= SEQUENCE (SIZE(0..MAX)) OF OCTET STRING (SIZE(0..MAX))

EndEntityType ::= BIT STRING {
    app     (0),
    enroll  (1)
} (SIZE (8))

-- =============================================================================
-- CRYPTOGRAPHIC ALGORITHMS
-- =============================================================================

HashAlgorithm ::= ENUMERATED {
    sha256,
    sha384,
    ...
}

-- =============================================================================
-- PUBLIC KEYS
-- =============================================================================

PublicVerificationKey ::= CHOICE {
    ecdsaNistP256         EccP256CurvePoint,
    ecdsaBrainpoolP256r1  EccP256CurvePoint,
    ecdsaBrainpoolP384r1  EccP384CurvePoint,
    ...
}

EccP256CurvePoint ::= CHOICE {
    x-only          OCTET STRING (SIZE (32)),
    fill            NULL,
    compressed-y-0  OCTET STRING (SIZE (32)),
    compressed-y-1  OCTET STRING (SIZE (32)),
    uncompressedP256 SEQUENCE {
        x OCTET STRING (SIZE (32)),
        y OCTET STRING (SIZE (32))
    }
}

EccP384CurvePoint ::= CHOICE {
    x-only          OCTET STRING (SIZE (48)),
    fill            NULL,
    compressed-y-0  OCTET STRING (SIZE (48)),
    compressed-y-1  OCTET STRING (SIZE (48)),
    uncompressedP384 SEQUENCE {
        x OCTET STRING (SIZE (48)),
        y OCTET STRING (SIZE (48))
    }
}

PublicEncryptionKey ::= SEQUENCE {
    supportedSymmAlg    SymmAlgorithm,
    publicKey           BasePublicEncryptionKey
}

BasePublicEncryptionKey ::= CHOICE {
    eciesNistP256         EccP256CurvePoint,
    eciesBrainpoolP256r1  EccP256CurvePoint,
    ...
}

SymmAlgorithm ::= ENUMERATED {
    aes128Ccm,
    ...
}

-- =============================================================================
-- SIGNATURES
-- =============================================================================

Signature ::= CHOICE {
    ecdsaNistP256Signature        EcdsaP256Signature,
    ecdsaBrainpoolP256r1Signature EcdsaP256Signature,
    ecdsaBrainpoolP384r1Signature EcdsaP384Signature,
    ...
}

EcdsaP256Signature ::= SEQUENCE {
    rSig    EccP256CurvePoint,
    sSig    OCTET STRING (SIZE (32))
}

EcdsaP384Signature ::= SEQUENCE {
    rSig    EccP384CurvePoint,
    sSig    OCTET STRING (SIZE (48))
}

-- =============================================================================
-- ENCRYPTION
-- =============================================================================

SymmetricCiphertext ::= CHOICE {
    aes128ccm           AesCcmCiphertext,
    ...
}

AesCcmCiphertext ::= SEQUENCE {
    nonce       OCTET STRING (SIZE (12)),
    ccmCiphertext Opaque
}

EncryptedData ::= SEQUENCE {
    recipients      SequenceOfRecipientInfo,
    ciphertext      SymmetricCiphertext
}

SequenceOfRecipientInfo ::= SEQUENCE OF RecipientInfo

RecipientInfo ::= CHOICE {
    pskRecipInfo        PreSharedKeyRecipientInfo,
    symmRecipInfo       SymmRecipientInfo,
    certRecipInfo       PKRecipientInfo,
    signedDataRecipInfo PKRecipientInfo,
    rekRecipInfo        PKRecipientInfo
}

PreSharedKeyRecipientInfo ::= HashedId8

SymmRecipientInfo ::= SEQUENCE {
    recipientId     HashedId8,
    encKey          SymmetricCiphertext
}

PKRecipientInfo ::= SEQUENCE {
    recipientId     HashedId8,
    encKey          EncryptedDataEncryptionKey
}

EncryptedDataEncryptionKey ::= CHOICE {
    eciesNistP256         EciesP256EncryptedKey,
    eciesBrainpoolP256r1  EciesP256EncryptedKey,
    ...
}

EciesP256EncryptedKey ::= SEQUENCE {
    v       EccP256CurvePoint,
    c       OCTET STRING (SIZE (16)),
    t       OCTET STRING (SIZE (16))
}

-- =============================================================================
-- CERTIFICATES
-- =============================================================================

Certificate ::= SEQUENCE {
    version                 Uint8 (3),
    type                    CertificateType,
    issuer                  IssuerIdentifier,
    toBeSigned              ToBeSignedCertificate,
    signature               Signature OPTIONAL
}

CertificateType ::= ENUMERATED {
    explicit,
    implicit,
    ...
}

IssuerIdentifier ::= CHOICE {
    sha256AndDigest         HashedId8,
    self                    HashAlgorithm,
    ...
}

ToBeSignedCertificate ::= SEQUENCE {
    id                      CertificateId,
    cracaId                 HashedId3,
    crlSeries               CrlSeries,
    validityPeriod          ValidityPeriod,
    region                  GeographicRegion OPTIONAL,
    assuranceLevel          SubjectAssurance OPTIONAL,
    appPermissions          SequenceOfPsidSsp OPTIONAL,
    certIssuePermissions    SequenceOfPsidGroupPermissions OPTIONAL,
    certRequestPermissions  SequenceOfPsidGroupPermissions OPTIONAL,
    canRequestRollover      NULL OPTIONAL,
    encryptionKey           PublicEncryptionKey OPTIONAL,
    verifyKeyIndicator      VerificationKeyIndicator,
    ...
}

CertificateId ::= CHOICE {
    linkageData             LinkageData,
    name                    Hostname,
    binaryId                OCTET STRING(SIZE(1..64)),
    none                    NULL,
    ...
}

Hostname ::= UTF8String (SIZE(0..255))

LinkageData ::= SEQUENCE {
    iCert                 IValue,
    linkage-value         LinkageValue,
    group-linkage-value   GroupLinkageValue OPTIONAL
}

IValue ::= Uint16
LinkageValue ::= OCTET STRING (SIZE(9))
GroupLinkageValue ::= SEQUENCE {
    jValue        OCTET STRING (SIZE(4)),
    value         OCTET STRING (SIZE(9))
}

CrlSeries ::= Uint16

VerificationKeyIndicator ::= CHOICE {
    verificationKey         PublicVerificationKey,
    reconstructionValue     EccP256CurvePoint,
    ...
}

-- =============================================================================
-- SIGNED DATA
-- =============================================================================

SignedData ::= SEQUENCE {
    hashId              HashAlgorithm,
    tbsData             ToBeSignedData,
    signer              SignerIdentifier,
    signature           Signature
}

ToBeSignedData ::= SEQUENCE {
    payload             SignedDataPayload,
    headerInfo          HeaderInfo
}

SignedDataPayload ::= SEQUENCE {
    data                Ieee1609Dot2Data OPTIONAL,
    extDataHash         HashedData OPTIONAL,
    ...
}

Ieee1609Dot2Data ::= SEQUENCE {
    protocolVersion     Uint8(3),
    content             Ieee1609Dot2Content
}

Ieee1609Dot2Content ::= CHOICE {
    unsecuredData               Opaque,
    signedData                  SignedData,
    encryptedData               EncryptedData,
    signedCertificateRequest    Opaque,
    ...
}

HashedData ::= CHOICE {
    sha256HashedData    OCTET STRING (SIZE(32)),
    sha384HashedData    OCTET STRING (SIZE(48)),
    ...
}

HeaderInfo ::= SEQUENCE {
    psid                        Psid,
    generationTime              Time64 OPTIONAL,
    expiryTime                  Time64 OPTIONAL,
    generationLocation          ThreeDLocation OPTIONAL,
    p2pcdLearningRequest        HashedId3 OPTIONAL,
    missingCrlIdentifier        MissingCrlIdentifier OPTIONAL,
    encryptionKey               EncryptionKey OPTIONAL,
    ...
}

ThreeDLocation ::= SEQUENCE {
    latitude            Latitude,
    longitude           Longitude,
    elevation           Elevation
}

Elevation ::= Uint16

MissingCrlIdentifier ::= SEQUENCE {
    cracaId             HashedId3,
    crlSeries           CrlSeries,
    ...
}

EncryptionKey ::= CHOICE {
    public                  PublicEncryptionKey,
    symmetric               SymmetricEncryptionKey
}

SymmetricEncryptionKey ::= CHOICE {
    aes128Ccm       OCTET STRING(SIZE(16)),
    ...
}

SignerIdentifier ::= CHOICE {
    digest              HashedId8,
    certificate         SequenceOfCertificate,
    self                NULL,
    ...
}

SequenceOfCertificate ::= SEQUENCE OF Certificate

END
